module router {
    yang-version 1;
    namespace "urn:sdnhub:odl:tutorial:router";
    prefix router;

    description "Router configuration";

    revision "2016-02-05" {
        description "Initial version.";
    }


    list interfaces {
        key id;
        leaf id {
            type string;
        }
        leaf ip-address {
            type string;
        }
    }

    container router {
        list ospf {
            key process-id;
            leaf process-id {
                type uint32;
            }
            list networks {
                key subnet-ip;
                leaf subnet-ip {
                    type string;
                }
                leaf area-id {
                    type uint32;
                }
            }
        }

        list bgp {
            key as-number;
            leaf as-number {
                type uint32;
            }
            leaf router-id {
                type string;
            }
            list neighbors {
                key as-number;
                leaf as-number {
                    type uint32;
                }
                leaf peer-ip {
                    type string;
                }
            }
        }
    }

    rpc make-toast {
     description
       "Make some toast. The toastDone notification will be sent when the toast is finished.
        An 'in-use' error will be returned if toast is already being made. A 'resource-denied' error will
        be returned if the toaster service is disabled.";

     input {
       leaf toasterDoneness {
         type uint32 {
           range "1 .. 10";
         }
         default '5';
         description
           "This variable controls how well-done is the ensuing toast. It should be on a scale of 1 to 10.
            Toast made at 10 generally is considered unfit for human consumption; toast made at 1 is warmed lightly.";
       }


     }
   }  // rpc make-toast

   // action to cancel making toast - takes no input parameters
   rpc cancel-toast {
     description
       "Stop making toast, if any is being made.
          A 'resource-denied' error will be returned
          if the toaster service is disabled.";
   }  // rpc cancel-toast
}
